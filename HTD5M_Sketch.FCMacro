from math import pi

# FreeCAD Helpers
def get_active_sketch():
	return FreeCAD.getDocument(FreeCAD.ActiveDocument.Name).getObject(FreeCAD.ActiveDocument.ActiveObject.Name)


def draw_circle(active_sketch, radius: float, is_construction: bool):
	circle = active_sketch.addGeometry(Part.Circle(App.Vector(0,0,0), App.Vector(0,0,1), radius), is_construction)
	update_drawing()
	return circle


def draw_line(active_sketch, start, end, is_construction):
	line = active_sketch.addGeometry(Part.LineSegment(App.Vector(start[0], start[1], 0), App.Vector(end[0], end[1], 0)), is_construction)
	update_drawing()
	return line

def draw_arc(active_sketch, center, radius, start_deg, end_deg, is_construction):
	arc = active_sketch.addGeometry(Part.ArcOfCircle(Part.Circle(App.Vector(center[0], center[1],0), App.Vector(0,0,1), radius), deg_to_rads(start_deg), deg_to_rads(end_deg)), is_construction)
	update_drawing()
	return arc


def update_drawing():
	App.ActiveDocument.recompute()


# Math Helpers
def pitch_diameter(tooth_count, tooth_pitch):
	return tooth_count * tooth_pitch / pi


def outside_diameter(pitch_diameter):
	pd_to_tooth = (3.81 - 2.08) / 2
	return pitch_diameter - (2 * pd_to_tooth)
	# TODO: make this calculation based on a lookup up the belt parameters per specification (3M, 5M, 8M, etc.)


def deg_to_rads(deg):
	return deg * pi / 180


# Main
def create_htd_pulley():
	# freecad vars
	active = get_active_sketch()

	# math vars
	pd = pitch_diameter(12, 5)
	od = outside_diameter(pd)

	# drawing
	outer_radius_line = draw_line(active, (0,0), (25,od), True)
	#tooth_flat = Part.ArcOfCircle(Part.Circle(App.Vector(0,0,0), App.Vector(0,0,1), od), deg_to_rads(90), deg_to_rads(80)), False)
	#tooth_small_curve = Part.ArcOfCircle(Part.Circle(App.Vector(0,0,0), App.Vector(0,0,1), od), deg_to_rads(90), deg_to_rads(80)), False)

	# constraints
	active.addConstraint(Sketcher.Constraint('Vertical', outer_radius_line))


create_htd_pulley()
FreeCAD.Console.PrintMessage("\nEnd\n")
